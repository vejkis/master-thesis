FME workspace Step3_download_from_NGP_convert_2D_and_3D.fmw
Description: Downloads objects from the NGP and converts them into 2D objects (for updating 2D municipal basemap) and 3D objects (for updating 3D city model).
Steps are further explained in section 4.7 Downloading NS Building datasets from NGP in Vejkdal Thorsberg (2025).
Vejkdal Thorsberg, O. (2025). Automatic geometry extraction in digital building permits: A case study using BIM and NS Building [Master's Degree, Lund University]. Master Thesis in Geographic Information Science #200. http://lup.lub.lu.se/student-papers/record/9215917
History: 2025-12-18,vejkis,Version 1: Published alongside master degree project.

Parameters:
- client_id =   # Consumer Key
- client_secret =   # Consumer Secret

Creator
    GEOMTYPE = Geometry Object
    NUM = 1
    CREATED -> AttributeCreator
Note: Export to format for updating 2D municipal basemap
Junction
Note: Export to format for updating 3D city model
Junction_2

Bookmark: Create attributes and encode text
AttributeCreator
    ATTR_TABLE = SET_TO ngp_login (varchar(57)) = $(client_id):$(client_secret)
    -> TextEncoder
TextEncoder
    DEST_ATTR = __authorizationkey
    ENCODING_TYPE = BASE64_ENCODE
    STRING_TO_ENCODE = @Value(ngp_login)
    -> HTTPCaller

Bookmark: Access token request
Note: Retrieve token
HTTPCaller
    ADDITIONAL_URL_PARAMETERS = grant_type;client_credentials
    CLIENT_CERTIFICATE_TYPE = NONE
    CONNECTION_TIMEOUT_LENGTH = 60
    CONTENT_TYPE_LOOKUP = text/plain
    CUSTOM_HEADERS = Authorization;Basic @Value(__authorizationkey)
    ERROR_ATTR = _error
    FOLLOW_REDIRECTS = FOLLOW_WITH_GET
    HTTP_METHOD = POST
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://apimanager-ver.lantmateriet.se/oauth2/token
    TRANSFER_TIMEOUT_LENGTH = 90
    UPLOAD_TYPE = STRING_UPLOAD
    USE_COOKIES = No
    VERIFY_SSL_CERTIFICATES = Yes
    UPLOAD_CONTENT_TYPE = Text (text/plain)
    -> JSONExtractor_Token
Note: Isolate access token
JSONExtractor_Token
    EXTRACT_QUERY_TABLE = _access_token json["access_token"]
    JSON_DOCUMENT = @Value(_response_body)
    READ_FROM_FILE = NO
    EVALUATED -> AttributeKeeper
Note: Remove unnecessary attributes
AttributeKeeper
    CREATE_BULK_MODE_FEATURES = NO
    KEEP_ATTRS = _access_token
    -> HTTPCaller_get_collections

Bookmark: Query reference objects
Note: Geodatakatalog Sökning API
HTTPCaller_get_collections
    CLIENT_CERTIFICATE_TYPE = NONE
    CONNECTION_TIMEOUT_LENGTH = 60
    CUSTOM_HEADERS = Authorization;Bearer @Value(_access_token)
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://api-ver.lantmateriet.se/distribution/geodatakatalog/sokning/v1/byggnad/v1/collections
    TRANSFER_TIMEOUT_LENGTH = 90
    USE_COOKIES = No
    VERIFY_SSL_CERTIFICATES = Yes
    -> JSONFragmenter_collections
Note: Split response into unique collections
JSONFragmenter_collections
    EXPLODE_FORMAT = JSON
    EXTRACT_ATTR = Yes
    JSON_ATTR = _response_body
    JSON_QUERY = json["collections"][*]
    NEW_ATTRIBUTES = collection_id buffer
    PREF_STRING = collection_
    READ_FROM_FILE = NO
    RECURSIVE = YES
    REJECT_EMPTY_LISTS = YES
    FRAGMENTS -> HTTPCaller_collectionid_items
Note: Geodatakatalog Sökning API
HTTPCaller_collectionid_items
    CLIENT_CERTIFICATE_TYPE = NONE
    CONNECTION_TIMEOUT_LENGTH = 60
    CUSTOM_HEADERS = Authorization;Bearer @Value(_access_token)
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://api-ver.lantmateriet.se/distribution/geodatakatalog/sokning/v1/byggnad/v1/collections/@Value(collection_id)/items
    TRANSFER_TIMEOUT_LENGTH = 90
    USE_COOKIES = No
    VERIFY_SSL_CERTIFICATES = Yes
    -> JSONFragmenter_items
Note: Split response into items per collection
JSONFragmenter_items
    EXPLODE_FORMAT = JSON
    EXTRACT_ATTR = Yes
    JSON_ATTR = _response_body
    JSON_QUERY = json["features"][*]
    NEW_ATTRIBUTES = properties.feature.typ buffer
    READ_FROM_FILE = NO
    RECURSIVE = YES
    REJECT_EMPTY_LISTS = YES
    FRAGMENTS -> JSONFragmenter_assets
Note: Split all assets for each respective item
JSONFragmenter_assets
    EXPLODE_FORMAT = JSON
    EXTRACT_ATTR = Yes
    JSON_ATTR = _response_body
    JSON_QUERY = json["assets"][*]
    NEW_ATTRIBUTES = asset_title buffer asset_href buffer
    PREF_STRING = asset_
    READ_FROM_FILE = NO
    RECURSIVE = YES
    REJECT_EMPTY_LISTS = YES
    FRAGMENTS -> Tester_7
Note: Isolate items that correspond to building components and asset link to original object
Tester_7
    BOOL_OP = AND
    TEST_CLAUSE:
      TEST @Value(properties.feature.typ) = byggnad
      TEST @Value(asset_title) = Byggnad
    TEST_MODE = TEST
    PASSED -> Tester_8
Note: Isolate Sandviken municipality
Tester_8
    BOOL_OP = OR
    TEST_CLAUSE = TEST @Value(collection_id) = 2181
    TEST_MODE = TEST
    PASSED -> HTTPCaller_original_object

Bookmark: Download original object
Note: Geodatakatalog Nedladdning API
HTTPCaller_original_object
    CLIENT_CERTIFICATE_TYPE = NONE
    CONNECTION_TIMEOUT_LENGTH = 60
    CUSTOM_HEADERS = Authorization;Bearer @Value(_access_token)
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = @Value(asset_href)
    TRANSFER_TIMEOUT_LENGTH = 90
    USE_COOKIES = No
    VERIFY_SSL_CERTIFICATES = Yes
    -> JSONFragmenter_components [off]

Bookmark: Merge individual components of original object into one object
Note: Split response into individual NS Building components
JSONFragmenter_components
    EXPLODE_FORMAT = JSON
    EXTRACT_ATTR = Yes
    JSON_ATTR = _response_body
    JSON_QUERY = json["features"][*]
    NEW_ATTRIBUTES = properties.feature:typ buffer properties.byggnadsdel buffer properties.planeradByggnadsdel buffer properties.variantNSLOD buffer properties.objektidentitet buffer properties.geometribeskrivning.geometri.absolutLagesosakerhetHojd buffer properties.geometribeskrivning.geometri.absolutLagesosakerhetPlan buffer properties.geometribeskrivning.geometrimetadata.lagesbestamningsmetodIHojd.typ buffer properties.geometribeskrivning.geometrimetadata.lagesbestamningsmetodIHojd.variant buffer properties.geometribeskrivning.geometrimetadata.lagesbestamningsmetodIPlan.typ buffer properties.geometribeskrivning.geometrimetadata.lagesbestamningsmetodIPlan.variant buffer properties.andamalskatalogreferens.kod buffer properties.byggnad.objektidentitet buffer
    READ_FROM_FILE = NO
    RECURSIVE = YES
    REJECT_EMPTY_LISTS = YES
    FRAGMENTS -> Tester_boundary_surface
Note: Isolate the components containing a geometry
Tester_boundary_surface
    BOOL_OP = OR
    TEST_CLAUSE = TEST @Value(properties.feature:typ) = takyta
    TEST_MODE = TEST
    PASSED -> FeatureMerger [REQUESTOR]
    FAILED -> FeatureMerger [SUPPLIER]
Note: Merge the attributes of the building parts onto the boundary surfaces (that contain geometries)
FeatureMerger
    ATTR_ACCUM_MODE = Merge Supplier
    ATTR_CONFLICT_RES_LOOKUP = REQUESTOR_IF_CONFLICT
    CLEANING_TOLERANCE_LOOKUP = AUTO
    CONNECT_Z_MODE_LOOKUP = FIRST_WINS
    GEOM_TYPE_VAL = POLYGONS
    IGNORE_NULLS = No
    JOIN_KEYS = @Value(properties.byggnadsdel) @Value(properties.objektidentitet) AUTO
    MERGE_TYPE = Attributes Only
    PROCESS_DUPS = YES
    REJECT_NULL_MISSING_KEYS = No
    SUPPLIERS_FIRST = No
    ATTR_CONFLICT_RES = Use Requestor
    CLEANING_TOLERANCE = Automatic
    CONNECT_Z_MODE = First Wins
    GEOM_TYPE = Build Polygons
    MERGED -> FeatureMerger_2 [REQUESTOR]
    UNUSED_SUPPLIER -> FeatureMerger_2 [SUPPLIER]
Note: Merge the attributes of the building onto the boundary surfaces (that contain geometries)
FeatureMerger_2
    ATTR_ACCUM_MODE = Merge Supplier
    ATTR_CONFLICT_RES_LOOKUP = REQUESTOR_IF_CONFLICT
    IGNORE_NULLS = No
    JOIN_KEYS = @Value(properties.byggnad.objektidentitet) @Value(properties.objektidentitet) AUTO
    MERGE_TYPE = Attributes Only
    PROCESS_DUPS = NO
    REJECT_NULL_MISSING_KEYS = No
    SUPPLIERS_FIRST = No
    ATTR_CONFLICT_RES = Use Requestor
    MERGED -> JSONExtractor_geometry

Bookmark: Handle geometry
Note: Expose geometry-attributes
JSONExtractor_geometry
    EXTRACT_QUERY_TABLE = geometri json["geometry"]
    JSON_DOCUMENT = @Value(_response_body)
    READ_FROM_FILE = NO
    EVALUATED -> GeometryReplacer_2
Note: Apply geometry onto the objects
GeometryReplacer_2
    KIND = GEOJSON
    REMOVE_ATTRIBUTE = Yes
    SOURCE = @Value(geometri)
    KIND_LONG = GeoJSON
    -> Reprojector
Note: Reproject to local projection zone
Reprojector
    DEST = EPSG:3010
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> 2DForcer
    REPROJECTED -> Dissolver_DTM
    REPROJECTED -> BoundsExtractor

Bookmark: Convert NS LOD 2.1b data to 2D data
Note: Remove z-values
2DForcer
    2D -> Dissolver
Note: Group on building part ID. / Specified tolerance (0.1m) removed any donuts
Dissolver
    ACCUM_INPUT_ATTRS = Use Attributes From One Feature
    CLEANING_TOLERANCE_LOOKUP = 0.1
    CONNECT_Z_MODE_LOOKUP = FIRST_WINS
    DEAGGREGATE_INPUT = Yes
    GROUP_BY = properties.byggnadsdel
    CLEANING_TOLERANCE = 0.1
    CONNECT_Z_MODE = First Wins
    AREA -> AttributeManager
Note: Set attributes according to municipal basemap
AttributeManager
    ATTR_TABLE:
      RENAME_SET_VALUE properties.andamalskatalogreferens.kod > bal_andamal (buffer) = Sporthall
      SET_TO bal_insamlingslage (varchar(200)) = FME_CONDITIONAL:DEFAULT_VALUE'Takkant'BOOL_OP;OR;COMPOSITE_TEST;1;TEST @Value(properties.planeradByggnadsdel) = Yes'Illustrativt läge'FME_NUM_CONDITIONS2___
      SET_TO bal_objektstatus (varchar(200)) = FME_CONDITIONAL:DEFAULT_VALUE'Gällande'BOOL_OP;OR;COMPOSITE_TEST;1;TEST @Value(properties.planeradByggnadsdel) = Yes'Planerad'FME_NUM_CONDITIONS2___
      RENAME_SET_VALUE properties.geometribeskrivning.geometri.absolutLagesosakerhetPlan > ge_lagesosakerhetplan (buffer)
      SET_TO ge_matmetodplan (varchar(15)) = konstruerad BIM
      REMOVE _access_token (varchar(200))
      REMOVE _response_body (buffer)
      REMOVE _http_status_code (buffer)
      REMOVE json_type (buffer)
      REMOVE json_index (uint32)
      REMOVE collection_id (buffer)
      REMOVE properties.feature.typ (buffer)
      REMOVE asset_title (buffer)
      REMOVE asset_href (buffer)
      REMOVE properties.feature:typ (buffer)
      RENAME_SET_VALUE properties.byggnadsdel > Objektidentitet (buffer)
      REMOVE properties.planeradByggnadsdel (buffer)
      REMOVE properties.variantNSLOD (buffer)
      REMOVE properties.objektidentitet (buffer)
      REMOVE properties.geometribeskrivning.geometri.absolutLagesosakerhetHojd (buffer)
      REMOVE properties.geometribeskrivning.geometrimetadata.lagesbestamningsmetodIHojd.typ (buffer)
      REMOVE properties.geometribeskrivning.geometrimetadata.lagesbestamningsmetodIHojd.variant (buffer)
      REMOVE properties.geometribeskrivning.geometrimetadata.lagesbestamningsmetodIPlan.typ (buffer)
      REMOVE properties.geometribeskrivning.geometrimetadata.lagesbestamningsmetodIPlan.variant (buffer)
      REMOVE properties.byggnad.objektidentitet (buffer)
    -> Junction

Bookmark: Convert NS LOD 2.1b data to 3D data
Note: Extract highest point (z-max) from each boundary surface
BoundsExtractor
    ZMAX = _zmax
    ZMIN = _zmin
    -> AttributeKeeper_3
Note: Removes unnecessary attributes
AttributeKeeper_3
    CREATE_BULK_MODE_FEATURES = NO
    KEEP_ATTRS = _zmax,_zmin,id,properties.byggnadsdel,properties.objektidentitet,properties.planeradByggnadsdel,properties.byggnad.objektidentitet
    -> FeatureMerger_3 [REQUESTOR]
Note: Adds ground level z-value to each roof surface
FeatureMerger_3
    ATTR_ACCUM_MODE = Merge Supplier
    ATTR_CONFLICT_RES_LOOKUP = REQUESTOR_IF_CONFLICT
    IGNORE_NULLS = No
    JOIN_KEYS = @Value(properties.byggnad.objektidentitet) @Value(properties.byggnad.objektidentitet) AUTO
    MERGE_TYPE = Attributes Only
    PROCESS_DUPS = NO
    REJECT_NULL_MISSING_KEYS = No
    SUPPLIERS_FIRST = No
    ATTR_CONFLICT_RES = Use Requestor
    MERGED -> ExpressionEvaluator
Note: Calculate difference in z between z-max and average z-value from DTM
ExpressionEvaluator
    ACTION = Create New Attribute
    EXPRESSION = @Value(_zmax)-@Value(elevation_m)
    VAL_ATTR = _z_extrusion
    -> 3DForcer
    -> Extruder
Note: Extruding roof surfaces downwards (negative z-direction)
Extruder
    DIRECTION_LOOKUP = VERTICAL
    DISTANCE = -(@Value(_z_extrusion)*1.5)
    DIRECTION = Vertical
    EXTRUDED -> GeometryValidator_3
Note: Translate 3D polygon to ground level, creating floor surface
3DForcer
    KEEPZVAL = No
    ZVALATTR = @Value(elevation_m)
    -> Extruder_2
Note: Extruding floor surfaces upwards (positive z-direction)
Extruder_2
    DIRECTION_LOOKUP = VERTICAL
    DISTANCE = (@Value(_z_extrusion)*1.5)
    DIRECTION = Vertical
    EXTRUDED -> GeometryValidator_2
Note: Set attributes according to 3D city model
AttributeManager_2
    ATTR_TABLE:
      REMOVE id (buffer)
      REMOVE properties.objektidentitet (buffer)
      RENAME_SET_VALUE properties.byggnadsdel > buildingpartID (buffer)
      RENAME_SET_VALUE properties.planeradByggnadsdel > plannedbuildingpart (buffer)
      REMOVE _zmin (real64)
      REMOVE _zmax (real64)
      REMOVE elevation_m (varchar(200))
      REMOVE _z_extrusion (real64)
      REMOVE _issues{}.count (uint32)
      REMOVE _issues{}.issue_found (buffer)
      REMOVE _issues{}.location_sample.x (real64)
      REMOVE _issues{}.location_sample.y (real64)
      REMOVE _issues{}.location_sample.z (real64)
      REMOVE _clipped (char(3))
    -> Junction_2

Bookmark: Extract surface footprint
Dissolver_DTM
    ACCUM_INPUT_ATTRS = Use Attributes From One Feature
    CLEANING_TOLERANCE_LOOKUP = 0.1
    CONNECT_Z_MODE_LOOKUP = IGNORE_Z
    DEAGGREGATE_INPUT = Yes
    CLEANING_TOLERANCE = 0.1
    CONNECT_Z_MODE = Ignore
    AREA -> Clipper_DTM [CLIPPER]

Bookmark: Calculate average z-value of ground level
Note: DTM input
Junction_3
    -> Clipper_DTM [CANDIDATE]
AttributeCreator_DTM_z-value
    ATTR_TABLE = SET_TO elevation_m (varchar(200)) = @Value(band0.mean)
    -> AttributeKeeper_2
Note: Removes unnecessary attributes
AttributeKeeper_2
    CREATE_BULK_MODE_FEATURES = NO
    KEEP_ATTRS = elevation_m,properties.byggnad.objektidentitet
    -> FeatureMerger_3 [SUPPLIER]

Bookmark: Extract average z-value from raster
Clipper_DTM
    ADD_NODATA = YES
    ATTR_ACCUM_MODE = MERGE
    ATTR_CONFLICT_RES = CANDIDATE
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> RasterStatisticsCalculator
RasterStatisticsCalculator
    RASTER_LEVEL = BAND_ONLY
    RASTER_STATS = "0   MEAN      "
    -> AttributeCreator_DTM_z-value

Bookmark: Attempt to correct 3D solids before clipper
GeometryValidator_3
    ISSUE_ATTR_NAME = _issues
    PRESETS = Surfaces And Solids
    REPAIR = Yes
    RULES = SELF_INTERSECTING CHECK_HOLE_TOUCHING_POLYGON]No]CONNECT_Z_MODE_SI]FIRST_WINS]SELF_INTERSECTION_TOLERANCE]None]INTERSECT_ACROSS_MULTIS]No]FME_CONTROLLER_QUERY_FILE]transformers/dependencies/geometryvalidator8/SELF_INTERSECTING.fme]FME_CONTROLLER_CHOICE]SELF_INTERSECTING PLANAR_SURFACE CHECK_AREA]DO_NOT_CHECK_AREA]TOLERANCE_MODE]AUTO]TOLERANCE]<Unused>]ANGULAR_TOLERANCE_MODE]AUTO]ANGULAR_TOLERANCE]<Unused>]FME_CONTROLLER_QUERY_FILE]transformers/dependencies/geometryvalidator8/PLANAR_SURFACE.fme]FME_CONTROLLER_CHOICE]PLANAR_SURFACE SOLID_VOID_REPAIR FME_CONTROLLER_QUERY_FILE]transformers/dependencies/geometryvalidator8/SOLID_VOID_REPAIR.fme]FME_CONTROLLER_CHOICE]SOLID_VOID_REPAIR SHELL_VALIDATION FLIP_APPEARANCE_MODE]FLIP_APPEARANCES]FME_CONTROLLER_QUERY_FILE]transformers/dependencies/geometryvalidator8/SHELL_VALIDATION.fme]FME_CONTROLLER_CHOICE]SHELL_VALIDATION MISSING_TEXTURE_COORDINATES FME_CONTROLLER_QUERY_FILE]transformers/dependencies/geometryvalidator8/MISSING_TEXTURE_COORDINATES.fme]FME_CONTROLLER_CHOICE]MISSING_TEXTURE_COORDINATES SURFACE_ORIENTATION FME_CONTROLLER_QUERY_FILE]transformers/dependencies/geometryvalidator8/SURFACE_ORIENTATION.fme]FME_CONTROLLER_CHOICE]SURFACE_ORIENTATION SOLID_ORIENTATION FME_CONTROLLER_QUERY_FILE]transformers/dependencies/geometryvalidator8/SOLID_ORIENTATION.fme]FME_CONTROLLER_CHOICE]SOLID_ORIENTATION
    SUMMARY = Detailed
    PASSED -> Clipper [CLIPPER]
    REPAIRED -> Clipper [CLIPPER]
GeometryValidator_2
    ISSUE_ATTR_NAME = _issues
    PRESETS = Surfaces And Solids
    REPAIR = Yes
    RULES = SELF_INTERSECTING CHECK_HOLE_TOUCHING_POLYGON]No]CONNECT_Z_MODE_SI]FIRST_WINS]SELF_INTERSECTION_TOLERANCE]None]INTERSECT_ACROSS_MULTIS]No]FME_CONTROLLER_QUERY_FILE]transformers/dependencies/geometryvalidator8/SELF_INTERSECTING.fme]FME_CONTROLLER_CHOICE]SELF_INTERSECTING PLANAR_SURFACE CHECK_AREA]DO_NOT_CHECK_AREA]TOLERANCE_MODE]AUTO]TOLERANCE]<Unused>]ANGULAR_TOLERANCE_MODE]AUTO]ANGULAR_TOLERANCE]<Unused>]FME_CONTROLLER_QUERY_FILE]transformers/dependencies/geometryvalidator8/PLANAR_SURFACE.fme]FME_CONTROLLER_CHOICE]PLANAR_SURFACE SOLID_VOID_REPAIR FME_CONTROLLER_QUERY_FILE]transformers/dependencies/geometryvalidator8/SOLID_VOID_REPAIR.fme]FME_CONTROLLER_CHOICE]SOLID_VOID_REPAIR SHELL_VALIDATION FLIP_APPEARANCE_MODE]FLIP_APPEARANCES]FME_CONTROLLER_QUERY_FILE]transformers/dependencies/geometryvalidator8/SHELL_VALIDATION.fme]FME_CONTROLLER_CHOICE]SHELL_VALIDATION MISSING_TEXTURE_COORDINATES FME_CONTROLLER_QUERY_FILE]transformers/dependencies/geometryvalidator8/MISSING_TEXTURE_COORDINATES.fme]FME_CONTROLLER_CHOICE]MISSING_TEXTURE_COORDINATES SURFACE_ORIENTATION FME_CONTROLLER_QUERY_FILE]transformers/dependencies/geometryvalidator8/SURFACE_ORIENTATION.fme]FME_CONTROLLER_CHOICE]SURFACE_ORIENTATION SOLID_ORIENTATION FME_CONTROLLER_QUERY_FILE]transformers/dependencies/geometryvalidator8/SOLID_ORIENTATION.fme]FME_CONTROLLER_CHOICE]SOLID_ORIENTATION
    SUMMARY = Detailed
    PASSED -> Clipper [CANDIDATE]
    REPAIRED -> Clipper [CANDIDATE]

Bookmark: Clip solids
Note: Clip both extrusions against each other, creating 3D object
Clipper
    ADD_NODATA = YES
    BOUNDARY_CASES = INSIDE
    CLEANING_TOLERANCE_LOOKUP = 0.1
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = 0.1
    MISSING_M_MODE = Linear Interpolation
    MISSING_Z_MODE = Planar Interpolation
    INSIDE -> GeometryValidator_4

Bookmark: Merge solids
Note: Isolate 3D objects that are correct which can be grouped/merged together
GeometryValidator_4
    ISSUE_ATTR_NAME = _issues
    PRESETS = Custom
    REPAIR = Yes
    RULES = SELF_INTERSECTING CHECK_HOLE_TOUCHING_POLYGON]No]CONNECT_Z_MODE_SI]FIRST_WINS]SELF_INTERSECTION_TOLERANCE]None]INTERSECT_ACROSS_MULTIS]No]FME_CONTROLLER_QUERY_FILE]transformers/dependencies/geometryvalidator8/SELF_INTERSECTING.fme]FME_CONTROLLER_CHOICE]SELF_INTERSECTING PLANAR_SURFACE CHECK_AREA]DO_CHECK_AREA]TOLERANCE_MODE]AUTO]TOLERANCE]<Unused>]ANGULAR_TOLERANCE_MODE]AUTO]ANGULAR_TOLERANCE]<Unused>]FME_CONTROLLER_QUERY_FILE]transformers/dependencies/geometryvalidator8/PLANAR_SURFACE.fme]FME_CONTROLLER_CHOICE]PLANAR_SURFACE SOLID_VOID_REPAIR FME_CONTROLLER_QUERY_FILE]transformers/dependencies/geometryvalidator8/SOLID_VOID_REPAIR.fme]FME_CONTROLLER_CHOICE]SOLID_VOID_REPAIR SHELL_VALIDATION FLIP_APPEARANCE_MODE]FLIP_APPEARANCES]FME_CONTROLLER_QUERY_FILE]transformers/dependencies/geometryvalidator8/SHELL_VALIDATION.fme]FME_CONTROLLER_CHOICE]SHELL_VALIDATION MISSING_TEXTURE_COORDINATES FME_CONTROLLER_QUERY_FILE]transformers/dependencies/geometryvalidator8/MISSING_TEXTURE_COORDINATES.fme]FME_CONTROLLER_CHOICE]MISSING_TEXTURE_COORDINATES SURFACE_ORIENTATION FME_CONTROLLER_QUERY_FILE]transformers/dependencies/geometryvalidator8/SURFACE_ORIENTATION.fme]FME_CONTROLLER_CHOICE]SURFACE_ORIENTATION SOLID_ORIENTATION FME_CONTROLLER_QUERY_FILE]transformers/dependencies/geometryvalidator8/SOLID_ORIENTATION.fme]FME_CONTROLLER_CHOICE]SOLID_ORIENTATION
    SUMMARY = Detailed
    PASSED -> SolidDissolver_2
Note: Groups or merges 3D solids based on building partID
SolidDissolver_2
    ACCUM_INPUT_ATTRS = ALL
    DEAGGREGATE_INPUT = Yes
    GROUP_BY = properties.planeradByggnadsdel
    SOLID -> AttributeManager_2
