FME workspace Step1_roof_extraction_map_attributes_to_NS_Building.fmw
Description: Extracts geometries equivalent to NS LOD 2.1b from IFC-models using FME.
Steps are further explained in sections 4.3-4.5 in Vejkdal Thorsberg (2025).
Vejkdal Thorsberg, O. (2025). Automatic geometry extraction in digital building permits: A case study using BIM and NS Building [Master's Degree, Lund University]. Master Thesis in Geographic Information Science #200. http://lup.lub.lu.se/student-papers/record/9215917
History: 2025-12-18,vejkis,Version 1: Published alongside master degree project.

Parameters:
- _subdivision = höjd   # Principle of sub-division
- _horizontal_reference = EPSG:3010   # Horizontal reference system (EPSG code)
- kod_andamalskatalogen = 020604   # Code in Boverket purpose catalogue
- ver_andamalskatalogen = 2   # Version of Boverket purpose catalogue
- _variantNSLOD = 2.1b   # NS LOD
- vertical_reference = EPSG:5613   # Vertical reference system (EPSG code)
- horizontal_gum = 0.5   # Measurement of uncertainty (in metres) in horizontal plane
- vertical_gum = 0.5   # Measurement of uncertainty (in metres) in z-direction
- _lagesbestamningsmetod_plan = lägesplacering   # Measurement method (horizontal plane)
- _lagesbestamningsmetod_hojd = lägesplacering   # Measurement method (z-direction)
- _variant_lagesbestamning_plan = 3D-modell   # Spatial alignment method (horizontal plane)
- _variant_lagesbestamning_hojd = 3D-modell   # Spatial alignment method (z-direction)

Note: IfcRoof input
Junction_5
    -> Tester_IfcRoof1
Note: IfcSlab input
Junction_4
    -> Tester_IfcSlab1
Note: IfcRoof input
Junction_3
    -> Tester_IfcRoof2
Note: IfcSlab input
Junction_2
    -> Tester_IfcSlab2

Bookmark: Arena Jernvallen
Tester_IfcRoof1
    BOOL_OP = OR
    TEST_CLAUSE = CASE_INSENSITIVE_TEST @Value(ObjectType) CONTAINS Ytter
    TEST_MODE = CASE_INSENSITIVE_TEST
    PASSED -> Deaggregator_BREP
Tester_IfcSlab1
    BOOL_OP = COMPOSITE
    COMPOSITE_TEST = 1 AND 2 AND 3 AND 4 AND 5
    TEST_CLAUSE:
      TEST @Value(PredefinedType) = ROOF
      CASE_INSENSITIVE_TEST @Value(ObjectType) NOT_CONTAINS Akustik
      CASE_INSENSITIVE_TEST @Value(ObjectType) NOT_CONTAINS Lutande
      CASE_INSENSITIVE_TEST @Value(ObjectType) NOT_CONTAINS Under trappa
      CASE_INSENSITIVE_TEST @Value(ObjectType) NOT_CONTAINS Takfot
    TEST_MODE = PER_TEST
    PASSED -> Deaggregator_BREP

Bookmark: Parkhallen
Tester_IfcSlab2
    BOOL_OP = OR
    TEST_CLAUSE = TEST @Value(PredefinedType) = ROOF
    TEST_MODE = TEST
    PASSED -> Tester_IfcRoof2
Tester_IfcRoof2
    BOOL_OP = OR
    TEST_CLAUSE:
      CASE_INSENSITIVE_TEST @Value(ObjectType) CONTAINS Inner
      CASE_INSENSITIVE_TEST @Value(ObjectType) CONTAINS tak
    TEST_MODE = CASE_INSENSITIVE_TEST
    FAILED -> Deaggregator_BREP

Bookmark: Extract roof surfaces
Note: Separate aggregate features into BRep solids
Deaggregator_BREP
    EXPLODE_INSTANCES = No
    GEOM_NAME_FIELD = _geometry_name
    LIST_ATTR_MODE_LOOKUP = LEAN
    RECURSIVE = Yes
    SPLIT_COMPOSITES = Yes
    MODE = Flatten All Levels
    DEAGGREGATED -> GeometryPartExtractor_BREP
Note: Separate solids into collection of surfaces (composite surfaces)
GeometryPartExtractor_BREP
    GQUERY:
      for $geom in //geometry
      where $geom/parent::geometry/@fme_geometry_name = 'Body'
      return number($geom/@fme_id)
    EXTRACTED -> Scaler_2
    EXTRACTED -> Scaler

Bookmark: Arena Jernvallen (already included spatial reference)
Note: Alter scale
Scaler_2
    DISABLE_FACTORIES = __DISABLED__
    RASTER_SCALING = Extents
    TEXT_LOC_ONLY = Location and Size
    XSCALE = 0.001
    YSCALE = 0.001
    ZSCALE = 0.001
    SCALE_ORIGIN = 0,0
    SCALED -> CoordinateSystemSetter_ArenaJernvallen
Note: Define coordinate system
CoordinateSystemSetter_ArenaJernvallen
    COORDSYS = EPSG:3010
    -> SurfaceFootprintReplacer_DTM
    -> BoundsExtractor

Bookmark: Parkhallen (did not contain spatial reference)
Note: Alter scale
Scaler
    DISABLE_FACTORIES = __DISABLED__
    RASTER_SCALING = Extents
    TEXT_LOC_ONLY = Location and Size
    XSCALE = 0.001
    YSCALE = 0.001
    ZSCALE = 0.001
    SCALE_ORIGIN = 0,0
    SCALED -> Offsetter
Note: Translation in X & Y to approximate location in SWEREF99 16 30
Offsetter
    MODE_LOOKUP = CARTESIAN
    XOFF = 151319
    YOFF = 6719599
    ZOFF = 0
    MODE = Cartesian Coordinate
    OFFSET -> CoordinateSystemSetter_Parkhallen
Note: Define coordinate system
CoordinateSystemSetter_Parkhallen
    COORDSYS = EPSG:3010
    -> SurfaceFootprintReplacer
    -> Affiner
Note: Similarity transformation, using coefficients calculated from AffineWarper
Affiner
    A = 0.9900906865937085
    B = 0.184965046868836
    C = -1241407.949261316
    D = -0.184965046868836
    E = 0.9900906865937085
    F = 94557.184716109
    AFFINED -> SurfaceFootprintReplacer_DTM
    AFFINED -> BoundsExtractor

Bookmark: Extract surface footprint
SurfaceFootprintReplacer_DTM
    OFFSET_Z_LOOKUP = 0
    SHADOW_TYPE = OVERHEAD
    OFFSET_Z = 0
    SHADOW_MODE = Overhead Shadow
    FOOTPRINT -> Dissolver_DTM
Dissolver_DTM
    ACCUM_INPUT_ATTRS = Use Attributes From One Feature
    CLEANING_TOLERANCE_LOOKUP = AUTO
    CONNECT_Z_MODE_LOOKUP = IGNORE_Z
    DEAGGREGATE_INPUT = Yes
    CLEANING_TOLERANCE = Automatic
    CONNECT_Z_MODE = Ignore
    AREA -> Clipper_DTM [CLIPPER]

Bookmark: Isolate 3D polygons
Note: Extract highest point from each composite surface
BoundsExtractor
    ZMAX = _z_max
    -> Deaggregator_CompositeSurfaces
Note: Separate composite surfaces into individual faces
Deaggregator_CompositeSurfaces
    EXPLODE_INSTANCES = No
    GEOM_NAME_FIELD = _geometry_name
    LIST_ATTR_MODE_LOOKUP = LEAN
    RECURSIVE = Yes
    SPLIT_COMPOSITES = Yes
    MODE = Flatten All Levels
    DEAGGREGATED -> SurfaceDissolver
Note: Group together coplanar faces that share a boundary and IfcGlobalUniqueId
SurfaceDissolver
    ACCUM_INPUT_ATTRS = Use Attributes From One Feature
    DEAGGREGATE_INPUT = Yes
    GROUP_BY = IfcGlobalIyUniqueId
    MATCHING_APPS = No
    NORMAL_TOLERANCE = 0
    OFFSET_TOLERANCE = 0
    SEPARATE_SURFACES = No
    SURFACE -> GeometryCoercer
Note: Remove appearances and sidedness from faces (converting to 3D polygon)
GeometryCoercer
    GQUERY:
      for $geom in //geometry
      where $geom/count(parent::geometry) = 0
      return number($geom/@fme_id)
    KIND = fme_polygon
    COERCED -> 2DForcer
    COERCED -> SurfaceDraper [POINTS/LINES]

Bookmark: Repair topological relationships in 2D between roof surfaces
2DForcer
    2D -> Dissolver_2Dpolygons
Note: Group together polygons that share a boundary and IfcGlobalUniqueId
Dissolver_2Dpolygons
    ACCUM_INPUT_ATTRS = Use Attributes From One Feature
    CLEANING_TOLERANCE_LOOKUP = AUTO
    CONNECT_Z_MODE_LOOKUP = IGNORE_Z
    DEAGGREGATE_INPUT = Yes
    GROUP_BY = IfcGlobalIyUniqueId
    CLEANING_TOLERANCE = Automatic
    CONNECT_Z_MODE = Ignore
    AREA -> Sorter_z_max
Note: Sort according to _z_max-value (descending)
Sorter_z_max
    SORT_PARM = _z_max NATURAL DESCENDING
    SORTED -> Counter_priority_attribute
Note: Create priority attribute according to sorting
Counter_priority_attribute
    CNT_ATTR = _rank_z_max
    DOMAIN = counter
    SCOPE = Global
    START = 0
    -> AreaGapAndOverlapCleaner
Note: Repairs 2D gaps and overlaps, retaining shape of polygons according to priority attribute
Note: Tolerance was set individually depending on dataset
AreaGapAndOverlapCleaner
    CLEANING_TOLERANCE_LOOKUP = 0.2
    CONNECT_Z_MODE_LOOKUP = IGNORE_Z
    DEAGGREGATE_INPUT = YES
    FILL_ALL_GAPS = Yes
    MEASURE_TYPE_LOOKUP = CONTINUOUS
    MISSING_VAL_MODE_LOOKUP = COMPUTE_NANS
    PRIORITY_ATTR = _rank_z_max
    REPAIR = PriorityAttribute
    CLEANING_TOLERANCE = 0.2
    CONNECT_Z_MODE = Ignore
    MEASURE_TYPE = Continuous
    MISSING_VAL_MODE = Compute
    REPAIR_METHOD = Priority (Edge Preserving)
    REPAIRED -> VariableRetriever_DTM_z-value

Bookmark: Translate 2D polygons in z-direction to ground level
VariableRetriever_DTM_z-value
    SCOPE = Global
    VALUE_ATTR = elevation_m
    VARNAME = elevation_m
    -> 3DForcer
3DForcer
    KEEPZVAL = No
    ZVALATTR = @Value(elevation_m)
    -> SurfaceDraper [DRAPE_FEATURES]

Bookmark: Repairing topological relationships between roof surfaces
Note: Drape polygons with contant z-value onto z-values from 3D polygons
SurfaceDraper
    ADDZ = YES
    DRAPE_TYPE = MODEL
    GROUP_BY = IfcGlobalIyUniqueId
    INTERPOLATION_TYPE = AUTO
    TOLERANCE = 0
    ADDZ_TYPE = Offset Z
    DRAPED_FEATURES -> SpatialRelator [Requestor]
    DRAPED_FEATURES -> SpatialFilter_2 [Candidate]

Bookmark: Export to QGIS for calculation of coefficients for similarity transformation
SurfaceFootprintReplacer
    OFFSET_Z_LOOKUP = 0
    SHADOW_TYPE = OVERHEAD
    OFFSET_Z = 0
    SHADOW_MODE = Overhead Shadow
    FOOTPRINT -> Dissolver
Dissolver
    ACCUM_INPUT_ATTRS = Use Attributes From One Feature
    CLEANING_TOLERANCE_LOOKUP = AUTO
    CONNECT_Z_MODE_LOOKUP = IGNORE_Z
    DEAGGREGATE_INPUT = Yes
    CLEANING_TOLERANCE = Automatic
    CONNECT_Z_MODE = Ignore
    AREA -> Junction_7
Note: Footprint of building was exported to QGIS to draw lines between corners of existing building in model and 2D municipal basemap.
Junction_7
    -> AffineWarper [CONTROL]
    -> AffineWarper [OBSERVED]
Note: Lines where then fed into this type of transformer to calculate the necessary coefficients
AffineWarper

Bookmark: Calculate average z-value of ground level
Note: DTM input
Junction_6
    -> Clipper_DTM [CANDIDATE]

Bookmark: Extract average z-value from raster
Clipper_DTM
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> RasterStatisticsCalculator
RasterStatisticsCalculator
    RASTER_LEVEL = BAND_ONLY
    RASTER_STATS = "0   MEAN      "
    -> VariableSetter_DTM_z-value
VariableSetter_DTM_z-value
    SCOPE = Global
    VALUE = @Value(band0.mean)
    VARNAME = elevation_m

Bookmark: Create attributes for building
Note: Creates one building instance
Creator_building
    GEOMTYPE = Geometry Object
    NUM = 1
    CREATED -> UniqueIdentifierGenerator_building
UniqueIdentifierGenerator_building
    UUID_ATTR = _uuid_building
    UUID_FORMAT = UUID_ONLY
    -> VariableSetter_uuid_building
VariableSetter_uuid_building
    SCOPE = Global
    VALUE = @Value(_uuid_building)
    VARNAME = _uuid_building
    -> AttributeCreator_building
Note: Creates attributes for building
AttributeCreator_building
    ATTR_TABLE:
      SET_TO _versionValidFrom (varchar(200)) = @DateTimeFormat(@DateTimeNow(local),ISO)
      SET_TO _purpose_catalog_json (varchar(200)) = {
        				"kod": "$(kod_andamalskatalogen)",
        				"version": $(ver_andamalskatalogen)
        }
      SET_TO _subdivision (varchar(200)) = $(_subdivision)
      SET_TO _horizontal_reference (varchar(200)) = $(_horizontal_reference)
    -> AttributeKeeper_rootelementJSON
    -> JSONTemplater [BUILDING]
Note: Isolates attributes to be merged in root element of JSON
AttributeKeeper_rootelementJSON
    CREATE_BULK_MODE_FEATURES = NO
    KEEP_ATTRS = _horizontal_reference,_uuid_building
    -> JSONTemplater [ROOT]

Bookmark: Creating attributes for building part
Note: 2D municipal basemap input
Junction
    -> SpatialFilter_2 [Filter]
Note: Spatial filter if roof surface intersects a building in 2D municipal basemap
SpatialFilter_2
    AGGREGATE_HANDLING = Yes
    BASE_TYPE = Multiple Filters
    CURVE_BOUNDARY_RULE_PARAM = Default Rule
    PASS_CRITERIA = Pass Against One Filter
    PREDICATES = INTERSECTS
    USE_BOUNDING_BOX = No
    PASSED -> AttributeCreator_false
    FAILED -> AttributeCreator_true
AttributeCreator_false
    ATTR_TABLE = SET_TO _planned_buildingpart (varchar(5)) = false
    -> Dissolver_buildingpart
AttributeCreator_true
    ATTR_TABLE = SET_TO _planned_buildingpart (varchar(5)) = true
    -> Dissolver_buildingpart
Note: Group together polygons that share a boundary and _planned_buildingpart
Dissolver_buildingpart
    ACCUM_INPUT_ATTRS = Use Attributes From One Feature
    CLEANING_TOLERANCE_LOOKUP = AUTO
    CONNECT_Z_MODE_LOOKUP = FIRST_WINS
    DEAGGREGATE_INPUT = Yes
    GROUP_BY = _planned_buildingpart
    CLEANING_TOLERANCE = Automatic
    CONNECT_Z_MODE = First Wins
    AREA -> UniqueIdentifierGenerator_buildingpart
Note: Merges attributes back onto 3D roof surfaces
UniqueIdentifierGenerator_buildingpart
    UUID_ATTR = _uuid_buildingpart
    UUID_FORMAT = UUID_ONLY
    -> AttributeCreator_nslod_buildingpart
Note: Creates attributes for building parts
AttributeCreator_nslod_buildingpart
    ATTR_TABLE = SET_TO _nslod_buildingpart (varchar(200)) = $(_variantNSLOD)
    -> AttributeKeeper_buildingpart
Note: Keeps only attributes connected to planned buildingpart, uuid, nslod
AttributeKeeper_buildingpart
    CREATE_BULK_MODE_FEATURES = NO
    KEEP_ATTRS = _planned_buildingpart,_uuid_buildingpart,_nslod_buildingpart
    -> SpatialRelator [Supplier]
    -> VariableRetriever_buildingpart
Note: Merges _uuid_building onto all building parts
VariableRetriever_buildingpart
    SCOPE = Global
    VALUE_ATTR = _uuid_building
    VARNAME = _uuid_building
    -> JSONTemplater [BUILDINGPART]

Bookmark: Mapping geometries and attributes to NS Building
SpatialRelator
    AGGREGATE_HANDLING = Yes
    ATTR_ACCUM_MODE = Merge Supplier
    ATTR_CONFLICT_RES = Use Requestor
    CALC_CARD = No
    CURVE_BOUNDARY_RULE_PARAM = Default Rule
    IGNORE_NULLS = Yes
    PREDICATES = INTERSECTS
    SUCCESS_ATTR = _related_suppliers
    -> GeometryExtractor

Bookmark: Extract geometries as GeoJSON and create attributes for roof surface
Note: Extracts geometries as GeoJSON
GeometryExtractor
    ATTR = _roofsurface_geojson
    JSON_MAX_DIGITS = 7
    KIND = GEOJSON
    REMOVE_GEOMETRY = No
    KIND_LONG = GeoJSON
    -> VariableRetriever_roofsurface
Note: Merges _uuid_building onto all roof surfaces
VariableRetriever_roofsurface
    SCOPE = Global
    VALUE_ATTR = _uuid_building
    VARNAME = _uuid_building
    -> AttributeCreator_roofsurface
Note: Creates attributes for roof surface
AttributeCreator_roofsurface
    ATTR_TABLE:
      SET_TO _uuid_roofsurface (varchar(200)) = @UUID()
      SET_TO _geometry_type (varchar(3)) = yta
      SET_TO _geometry_dimension (uint8) = 3
      SET_TO _geometry_horizontal_reference (varchar(200)) = $(_horizontal_reference)
      SET_TO _geometry_vertical_reference (varchar(200)) = $(vertical_reference)
      SET_TO _roofsurface_type (varchar(12)) = hela takytan
      SET_TO _geometry_horizontal_gum (varchar(200)) = $(horizontal_gum)
      SET_TO _geometry_vertical_gum (varchar(200)) = $(vertical_gum)
      SET_TO _hojdlageTak (varchar(9)) = totalhöjd
      SET_TO _geometrymetadata (varchar(200)) = {
        				"tidpunktForLagesbestamning": "@DateTimeFormat(@DateTimeNow(local),ISO)",
                        "tidpunktForKontrollAvGeometri": "@DateTimeFormat(@DateTimeNow(local),ISO)",
                        "ansvarigOrganisation": {
                            "organisationsnamn": "Sandvikens kommun",
                            "organisationsnummer": "212000-2346"
                        },
                        "utforandeOrganisation": {
                            "organisationsnamn": "Sandvikens kommun",
                            "organisationsnummer": "212000-2346"
                        },
                        "lagesbestamningsmetodIPlan": {
        					"typ": "$(_lagesbestamningsmetod_plan)",
        					"variant": "$(_variant_lagesbestamning_plan)"
        				},
        				"lagesbestamningsmetodIHojd": {
        					"typ": "$(_lagesbestamningsmetod_hojd)",
        					"variant": "$(_variant_lagesbestamning_hojd)"
                            }
        }
    -> AttributeKeeper_roofsurface
Note: Isolates attributes to be merged in roofsurface element of JSON
AttributeKeeper_roofsurface
    CREATE_BULK_MODE_FEATURES = NO
    KEEP_ATTRS = _geometry_dimension,_geometry_horizontal_gum,_geometry_horizontal_reference,_geometry_type,_geometry_vertical_gum,_geometry_vertical_reference,_geometrymetadata,_roofsurface_geojson,_roofsurface_type,_uuid_buildingpart,_uuid_roofsurface
    -> JSONTemplater [ROOFSURFACE]

Bookmark: Create GeoJSON file
Note: Merge objects into JSON
JSONTemplater
    BUILDINGPART_QUERY_EXPR:
      {
          "type": "Feature",
          "id": fme:get-attribute("_uuid_buildingpart"),
          "geometry": null,
          "properties": {
                  "feature:typ": "byggnadsdel",
                  "objektidentitet": fme:get-attribute("_uuid_buildingpart"),
                  "byggnad": fme:get-attribute("_uuid_building"),
                  "variantNSLOD": fme:get-attribute("_nslod_buildingpart"),
                  "planeradByggnadsdel": xs:boolean(fme:get-attribute("_planned_buildingpart"))
                  }
      }
    BUILDING_QUERY_EXPR:
      {
          "type": "Feature",
          "id": fme:get-attribute("_uuid_building"),
          "geometry": null,
          "properties": {
                  "feature:typ": "byggnad",
                  "objektidentitet": fme:get-attribute("_uuid_building"),
                  "versionGiltigFran": fme:get-attribute("_versionValidFrom"),
                  "andamalskatalogreferens": fme:get-attribute("_purpose_catalog_json"),
                  "indelningsgrund": fme:get-attribute("_subdivision")
          }
      }
    CONSECUTIVE_GROUPS = No
    GROUP_BY = _uuid_building
    RESULT_ATTRIBUTE = _result
    ROOFSURFACE_QUERY_EXPR:
      {
          "type": "Feature",
          "id": fme:get-attribute("_uuid_roofsurface"),
          "geometry": {
              fme:get-attribute("_roofsurface_geojson")
            },
          "properties": {
              "feature:typ": "takyta",
              "objektidentitet": fme:get-attribute("_uuid_roofsurface"),
              "byggnadsdel": fme:get-attribute("_uuid_buildingpart"),
              "geometribeskrivning": {
                          "geometri": {
                              "typ": fme:get-attribute("_geometry_type"),
                              "absolutLagesosakerhetPlan": fn:round(fme:get-attribute("_geometry_horizontal_gum"), 2),
                              "absolutLagesosakerhetHojd": fn:round(fme:get-attribute("_geometry_vertical_gum"), 2),
                              "koordinatsystemPlan": fme:get-attribute("_geometry_horizontal_reference"),
                              "hojdsystem": fme:get-attribute("_geometry_vertical_reference"),
                              "dimension": fme:get-attribute("_geometry_dimension")
                          },
                          "geometrimetadata": fme:get-attribute("_geometrymetadata")
              },
                          "takdel": fme:get-attribute("_roofsurface_type")
          }
      }
    ROOT_QUERY_EXPR:
      {
      	"type": "FeatureCollection",
      	"crs": {
      		"type": "name",
      		"properties": {
      			"name": fme:get-attribute("_horizontal_reference")
      		}
      	},
      	"feature:mediatyp": "application/vnd.lm.byggnad.v1+json",
      	"features": [
          fme:process-features("BUILDING"),
          fme:process-features("BUILDINGPART"),
          fme:process-features("ROOFSURFACE")
          ]

      }
    VISIBLE_QUERY_VALIDATE = Yes
    -> JSONFormatter
Note: Formats JSON-file correctly
JSONFormatter
    ERROR_LIST_ATTR = _json_error
    FORMAT_LOOKUP = PRETTY_PRINT
    INDENT_SIZE = 3
    JSON_DOCUMENT = @Value(_result)
    OUTPUT_ATTR = text_line_data
    OUTPUT_ENCODING = UTF-8
    READ_FROM_FILE = NO
    REMOVE_EMPTY_OBJECTS_AND_ARRAYS_LOOKUP = YES
    REMOVE_EMPTY_STRINGS_LOOKUP = YES
    REMOVE_NULLS_LOOKUP = NO
    FORMAT = Pretty Print
    INDENT_STYLE = 3 spaces
    REMOVE_EMPTY_OBJECTS_AND_ARRAYS = Yes
    REMOVE_EMPTY_STRINGS = Yes
    REMOVE_NULLS = No
    -> JSONValidator
Note: Validates syntax of JSON file
JSONValidator
    ERROR_LIST_ATTR = _json_error
    JSON_DOCUMENT = @Value(_result)
    READ_FROM_FILE = NO
    PASSED -> AttributeKeeper_GeoJSON
Note: Removes unneccesary attributes before writing to GeoJSON file
AttributeKeeper_GeoJSON
    CREATE_BULK_MODE_FEATURES = NO
    KEEP_ATTRS = text_line_data
    -> Junction_8
Note: GeoJSON export
Junction_8
