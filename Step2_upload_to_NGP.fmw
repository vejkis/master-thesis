FME workspace Step2_upload_to_NGP.fmw
Description: Uploads objects to the NGP.
Steps are further explained in section 4.6 Validating and uploading NS Building datasets to NGP in Vejkdal Thorsberg (2025).
Vejkdal Thorsberg, O. (2025). Automatic geometry extraction in digital building permits: A case study using BIM and NS Building [Master's Degree, Lund University]. Master Thesis in Geographic Information Science #200. http://lup.lub.lu.se/student-papers/record/9215917
History: 2025-12-18,vejkis,Version 1: Published alongside master degree project.

Parameters:
- Kommun = 1284
- client_id =   # Consumer Key
- client_secret =   # Consumer Secret

Note: GeoJSON input
Junction
    -> AttributeFileReader

Bookmark: Initiate call to Lantmäteriets National Geodata Platform (NGP)
Call_Lantmäteriet: Creator
    GEOMTYPE = Geometry Object
    NUM = 1
    CREATED -> LantmaterietAPIAccessTokenFetcher
Note: Creates and fetches access token to Lantmäteriet
LantmaterietAPIAccessTokenFetcher
    API_BASE_URL = https://apimanager-ver.lantmateriet.se/
    API_KEY = $(client_id)
    API_SECRET = $(client_secret)
    API_TOKEN_REVOKE_URL = oauth2/revoke
    API_TOKEN_URL = oauth2/token
    MINIMUM_TOKEN_LIFETIME = 1800
    OutputWithToken -> AttributeCreator_token_join1

Bookmark: Add dummy value to join token and input
AttributeCreator_token_join1
    ATTR_TABLE = SET_TO _join (uint64) = 1
    -> FeatureJoiner [LEFT]
AttributeCreator_token_join2
    ATTR_TABLE = SET_TO _join (uint64) = 1
    -> FeatureJoiner [RIGHT]

Bookmark: Input from Step 1 FME Workspace
Note: Reads the contents of GeoJSON as attributes
AttributeFileReader
    CHAR_ENCODING = utf-8
    DEST_ATTR = _file_contents
    FILE_NAME = @Value(fme_dataset)
    -> AttributeFilter
Note: Isolates building-component
AttributeFilter
    ATTR_NAME = feature:typ
    ATTR_VALUES = <Empty>,<Missing>,<Null>,<Unfiltered>,byggnad,byggnadsdel,bottenyta,takyta
    PRESERVE_FEATURE_ORDER_LOOKUP = PER_OUTPUT_PORT
    byggnad -> AttributeCreator_token_join2

Bookmark: Adds API Access token to inputs
Note: Merges acces token on feature
FeatureJoiner
    ATTR_CONFLICT_RES_LOOKUP = USE_LEFT
    GEOMETRY_HANDLING_LOOKUP = USE_LEFT
    JOIN_KEYS = _join _join AUTO
    JOIN_MODE = Inner
    ATTR_CONFLICT_RES = Prefer Left
    GEOMETRY_HANDLING = Prefer Left
    JOINED -> HTTPCaller_set_up_reception

Bookmark: Registers a reception and a change to the NGP
Note: Generates receptionID and reception status
HTTPCaller_set_up_reception
    CLIENT_CERTIFICATE_TYPE = NONE
    CONNECTION_TIMEOUT_LENGTH = 60
    CONTENT_TYPE_LOOKUP = application/json
    CUSTOM_HEADERS = Authorization;Bearer @Value(_access_token)
    ERROR_ATTR = _error
    FOLLOW_REDIRECTS = DO_NOT_FOLLOW
    HTTP_METHOD = POST
    MAX_HTTP_VERSION = HTTP_2
    MAX_TRANSFERS_IN_PROGRESS = 25
    MINIMUM_ENCRYPTION_LEVEL = OS_DEFAULT
    RESPONSE_TYPE = Attribute
    SPLIT_MULTIPART_DOWNLOADS = NO
    STATUS_CODE_ATTR = _http_status_code
    TARGET_ATTR = _response_body
    TARGET_ATTR_ENCODING = auto-detect
    TARGET_URL = https://api-ver.lantmateriet.se/distribution/geodatakatalog/uppdatering/v1/mottagning
    TRANSFER_TIMEOUT_LENGTH = 90
    UPLOAD_BODY:
      {
          "leveransinfo": {
              "informationstyp": "byggnad",
              "provider": "$(Kommun)"
           }
      }
    UPLOAD_TYPE = STRING_UPLOAD
    USE_COOKIES = No
    VERIFY_SSL_CERTIFICATES = Yes
    UPLOAD_CONTENT_TYPE = JSON (application/json)
    -> JSONExtractor
Note: Isolates receptionID and receptionStatus
JSONExtractor
    EXTRACT_QUERY_TABLE = receptionID JSON["id"] receptionStatus JSON["status"]["typ"]
    JSON_DOCUMENT = @Value(_response_body)
    READ_FROM_FILE = NO
    EVALUATED -> AttributeRemover_reception
Note: Removes unnecessary attributes
AttributeRemover_reception
    REMOVE_ATTRS = _expires_in,_http_status_code,_join,_response_body,_scope,_token_type,receptionStatus
    -> HTTPCaller_register_changes
Note: Register change
HTTPCaller_register_changes
    CLIENT_CERTIFICATE_TYPE = NONE
    CONNECTION_TIMEOUT_LENGTH = 60
    CONTENT_TYPE_LOOKUP = application/json
    CUSTOM_HEADERS = Authorization;Bearer @Value(_access_token)
    ERROR_ATTR = _error
    FOLLOW_REDIRECTS = DO_NOT_FOLLOW
    HTTP_METHOD = POST
    MAX_HTTP_VERSION = HTTP_1_1
    MAX_TRANSFERS_IN_PROGRESS = 25
    MINIMUM_ENCRYPTION_LEVEL = OS_DEFAULT
    RESPONSE_TYPE = Attribute
    SPLIT_MULTIPART_DOWNLOADS = NO
    STATUS_CODE_ATTR = _http_status_code
    TARGET_ATTR = _response_body
    TARGET_ATTR_ENCODING = auto-detect
    TARGET_URL = https://api-ver.lantmateriet.se/distribution/geodatakatalog/uppdatering/v1/mottagning/@Value(receptionID)/forandringar
    TRANSFER_TIMEOUT_LENGTH = 90
    UPLOAD_BODY:
      {
        "forandringar": [
          {
            "objektidentitet": "@Value(objektidentitet)",
            "typ": "leverans"
          }
        ]
      }
    UPLOAD_TYPE = STRING_UPLOAD
    USE_COOKIES = No
    VERIFY_SSL_CERTIFICATES = Yes
    UPLOAD_CONTENT_TYPE = JSON (application/json)
    -> JSONExtractor_2
Note: Isolates changeID, changeStatus, changeType.
JSONExtractor_2
    EXTRACT_QUERY_TABLE = changeType JSON["forandringar"][0]["typ"] changeStatus JSON["forandringar"][0]["status"]["typ"] changeID JSON["forandringar"][0]["objektidentitet"]
    JSON_DOCUMENT = @Value(_response_body)
    READ_FROM_FILE = NO
    EVALUATED -> AttributeRemover_register_changes
Note: Removes unnecessary attributes
AttributeRemover_register_changes
    REMOVE_ATTRS = _http_status_code,_response_body,changeType
    -> HTTPCaller_upload

Bookmark: Uploading the building object
Note: Upload objects
HTTPCaller_upload
    CLIENT_CERTIFICATE_TYPE = NONE
    CONNECTION_TIMEOUT_LENGTH = 60
    CONTENT_TYPE_LOOKUP = application/vnd.lm.byggnad.v1+json
    CUSTOM_HEADERS = Authorization;Bearer @Value(_access_token)
    ERROR_ATTR = _error
    FOLLOW_REDIRECTS = DO_NOT_FOLLOW
    HTTP_METHOD = POST
    MAX_HTTP_VERSION = HTTP_2
    MAX_TRANSFERS_IN_PROGRESS = 25
    MINIMUM_ENCRYPTION_LEVEL = OS_DEFAULT
    RESPONSE_TYPE = Attribute
    SPLIT_MULTIPART_DOWNLOADS = NO
    STATUS_CODE_ATTR = _http_status_code
    TARGET_ATTR = _response_body
    TARGET_ATTR_ENCODING = auto-detect
    TARGET_URL = https://api-ver.lantmateriet.se/distribution/geodatakatalog/uppdatering/v1/mottagning/@Value(receptionID)/forandringar/@Value(objektidentitet)/leverans
    TRANSFER_TIMEOUT_LENGTH = 90
    UPLOAD_BODY = @Value(_file_contents)
    UPLOAD_TYPE = STRING_UPLOAD
    USE_COOKIES = No
    VERIFY_SSL_CERTIFICATES = Yes
    UPLOAD_CONTENT_TYPE = application/vnd.lm.byggnad.v1+json
    -> JSONExtractor_3
Note: Isolates links to object
JSONExtractor_3
    EXTRACT_QUERY_TABLE = _href JSON["href"]
    JSON_DOCUMENT = @Value(_response_body)
    READ_FROM_FILE = NO
    EVALUATED -> AttributeRemover_upload
Note: Removes unnecessary attributes
AttributeRemover_upload
    REMOVE_ATTRS = _http_status_code,changeStatus
    -> FeatureHolder

Bookmark: Waiting for objects to be uploaded and LM to validate the objects
Note: Waits until all objects have been processed
FeatureHolder
    -> Sampler
Note: Picks one random object
Sampler
    MODE = ORIGINAL
    RATE = 1
    SAMPLE_TYPE_MULTIPLIER = -1
    SAMPLE_MODE = No
    SAMPLE_TYPE_LONG = First N Features
    SAMPLED -> Decelerator
    NOT_SAMPLED -> FeatureHolder_2
Note: Object creates delay
Decelerator
    DECEL_LOOKUP = PERFEATDELAY
    DELAY = 10
    DECEL_TYPE = Per Feature Delay
    -> FeatureHolder_2
Note: Waits until all objects have been received, including the delayed one
FeatureHolder_2
    -> HTTPCaller_get_validation_report

Bookmark: Retrieve validation report on object
Note: Gets validation report on uploaded objects
HTTPCaller_get_validation_report
    CLIENT_CERTIFICATE_TYPE = NONE
    CONNECTION_TIMEOUT_LENGTH = 60
    CUSTOM_HEADERS = Authorization;Bearer @Value(_access_token)
    ERROR_ATTR = _error
    FOLLOW_REDIRECTS = DO_NOT_FOLLOW
    HTTP_METHOD = GET
    MAX_HTTP_VERSION = HTTP_2
    MAX_TRANSFERS_IN_PROGRESS = 25
    MINIMUM_ENCRYPTION_LEVEL = OS_DEFAULT
    RESPONSE_TYPE = Attribute
    SPLIT_MULTIPART_DOWNLOADS = NO
    STATUS_CODE_ATTR = _http_status_code
    TARGET_ATTR = _response_body
    TARGET_ATTR_ENCODING = auto-detect
    TARGET_URL = https://api-ver.lantmateriet.se/distribution/geodatakatalog/uppdatering/v1/mottagning/@Value(receptionID)/forandringar/@Value(objektidentitet)/leverans
    TRANSFER_TIMEOUT_LENGTH = 90
    USE_COOKIES = No
    VERIFY_SSL_CERTIFICATES = Yes
    -> AttributeRemover_validation_report
Note: Removes unnecessary attributes
AttributeRemover_validation_report
    REMOVE_ATTRS = _access_token,_href,_http_status_code,receptionID
    -> ValidationReport
Note: Inspector to view the validation report
ValidationReport: Inspector

FME custom transformer LantmaterietAPIAccessTokenFetcher
LantmaterietAPIAccessTokenFetcher
Generates an Access Token for API:s from Lantmäteriet, the Swedish mapping, cadastral and land registration authority.
If the token received expires too soon, it is revoked and a new token is generated.
This transformer can be used on its own to generate authentication for Lantmäteriet's API:s.
It can also be used together with the following transformers to handle downloads from the "Geotorget-Order - v2" API:
LantmaterietAPIDeliveryRequestor
LantmaterietAPIDownloadLinkFetcher
Create an Application, subscribe to the relevant API:s and generate keys for your application at:
https://apimanager.lantmateriet.se/store/
Input the application's Consumer Key and Consumer Secret as parameters.
Parameters
API_KEY
"Consumer Key" from the Application at https://apimanager.lantmateriet.se/store.
API_SECRET
"Consumer Secret" from the Application at https://apimanager.lantmateriet.se/store.
OPTIONAL_SCOPE
A single application may generate tokens for multiple scopes (e g for multiple clients). Tokens generated for a specific scope must be used along with their scopes in further requests.
API_BASE_URL
The base URL for the API endpoints, e g https://api.lantmateriet.se
API_TOKEN_URL
The API's token generation endpoint (excluding the base URL)
API_TOKEN_REVOKE_URL
The API's endpoint for revoking tokens (excluding the base URL)
MINIMUM_TOKEN_LIFETIME
Tokens with expires_in less than this number will be revoked and a new token is generated.
License
MIT License
Copyright © 2021, Mattias Spångmyr, Haninge kommun.
Permission is hereby granted, free of charge, to any person obtaining a copy
of this software and associated documentation files (the "Software"), to deal
in the Software without restriction, including without limitation the rights
to use, copy, modify, merge, publish, distribute, sublicense, and/or sell
copies of the Software, and to permit persons to whom the Software is
furnished to do so, subject to the following conditions:
The above copyright notice and this permission notice shall be included in all
copies or substantial portions of the Software.
THE SOFTWARE IS PROVIDED "AS IS", WITHOUT WARRANTY OF ANY KIND, EXPRESS OR
IMPLIED, INCLUDING BUT NOT LIMITED TO THE WARRANTIES OF MERCHANTABILITY,
FITNESS FOR A PARTICULAR PURPOSE AND NONINFRINGEMENT. IN NO EVENT SHALL THE
AUTHORS OR COPYRIGHT HOLDERS BE LIABLE FOR ANY CLAIM, DAMAGES OR OTHER
LIABILITY, WHETHER IN AN ACTION OF CONTRACT, TORT OR OTHERWISE, ARISING FROM,
OUT OF OR IN CONNECTION WITH THE SOFTWARE OR THE USE OR OTHER DEALINGS IN THE
SOFTWARE.

Parameters:
- API_KEY =   # API Consumer Key
- API_SECRET =   # API Consumer Secret
- OPTIONAL_SCOPE =   # If the application requires a scope, input the scope here
- API_BASE_URL = https://api.lantmateriet.se   # URL for LM's API
- API_TOKEN_URL = /token   # Access Token Request URL
- API_TOKEN_REVOKE_URL = /revoke   # Access Token Revoke Request URL
- MINIMUM_TOKEN_LIFETIME = 1800   # Minimum seconds left on token before regenerating

Creator_AccessToken
    GEOMTYPE = Geometry Object
    NUM = 1
    CREATED -> AttributeCreator_AuthorizationKey
RetryAfterRevokation (input)
    -> HTTPCaller_GenerateAccessToken
Note: Request a new Access Token
HTTPCaller_GenerateAccessToken
    ADDITIONAL_URL_PARAMETERS = grant_type;client_credentials scope;$(OPTIONAL_SCOPE)
    CONNECTION_TIMEOUT_LENGTH = 60
    CONTENT_TYPE_LOOKUP = text/plain
    CUSTOM_HEADERS = Authorization;Basic @Value(__authorizationkey)
    ERROR_ATTR = __error
    FOLLOW_REDIRECTS = Yes
    HTTP_METHOD = POST
    SAVE_FILE_LOOKUP = NO
    STATUS_CODE_ATTR = __http_status_code
    TARGET_ATTR = __response_body
    TARGET_ATTR_ENCODING = auto-detect
    TARGET_URL = $(API_BASE_URL)$(API_TOKEN_URL)
    TRANSFER_TIMEOUT_LENGTH = 90
    UPLOAD_TYPE = Specify Upload Body
    USE_COOKIES = No
    VERIFY_SSL_CERTIFICATES = Yes
    SAVE_FILE = Attribute
    UPLOAD_CONTENT_TYPE = Text (text/plain)
    -> JSONExtractor_Token
Note: Extract the response values
JSONExtractor_Token
    EXTRACT_QUERY_TABLE = _access_token json["access_token"] _scope json["scope"] _token_type json["token_type"] _expires_in json["expires_in"]
    JSON_DOCUMENT = @Value(__response_body)
    READ_FROM_FILE = NO
    EVALUATED -> Tester_TokenExpiresSoon
Note: Check if the token is expiring soon
Tester_TokenExpiresSoon
    BOOL_OP = OR
    TEST_CLAUSE = TEST @Value(_expires_in) < $(MINIMUM_TOKEN_LIFETIME)
    TEST_MODE = TEST
    PASSED -> HTTPCaller_RevokeAccessToken
    FAILED -> AttributeCreator_ResultDummyValue
Note: Revoke an old access token so that a new one can be generated.
HTTPCaller_RevokeAccessToken
    ADDITIONAL_URL_PARAMETERS = token;@Value(_access_token)
    CONNECTION_TIMEOUT_LENGTH = 60
    CONTENT_TYPE_LOOKUP = text/plain
    CUSTOM_HEADERS = Authorization;Basic @Value(__authorizationkey)
    ERROR_ATTR = __error
    FOLLOW_REDIRECTS = Yes
    HTTP_METHOD = POST
    SAVE_FILE_LOOKUP = NO
    STATUS_CODE_ATTR = __http_status_code
    TARGET_ATTR = __response_body
    TARGET_ATTR_ENCODING = auto-detect
    TARGET_URL = $(API_BASE_URL)$(API_TOKEN_REVOKE_URL)
    TRANSFER_TIMEOUT_LENGTH = 90
    UPLOAD_TYPE = Specify Upload Body
    USE_COOKIES = No
    VERIFY_SSL_CERTIFICATES = Yes
    SAVE_FILE = Attribute
    UPLOAD_CONTENT_TYPE = Text (text/plain)
    -> RetryAfterRevokation (output)
RetryAfterRevokation (output)
Note: Add a dummy value to let the result be joined to each input feature
AttributeCreator_ResultDummyValue
    ATTR_TABLE = SET_TO __dummyvalue = 1
    -> FeatureJoiner_JoinTokenToInput [RIGHT]
Note: Input features to receive the access token
Input (input)
    -> AttributeCreator_InputDummyValue
Note: Add a dummy value to let each input feature be joined to the result in a many-to-one join.
AttributeCreator_InputDummyValue
    ATTR_TABLE = SET_TO __dummyvalue = 1
    -> FeatureJoiner_JoinTokenToInput [LEFT]
FeatureJoiner_JoinTokenToInput
    ATTR_CONFLICT_RES_LOOKUP = USE_LEFT
    GEOMETRY_HANDLING_LOOKUP = USE_LEFT
    JOIN_KEYS = __dummyvalue __dummyvalue AUTO
    JOIN_MODE = Left
    ATTR_CONFLICT_RES = Use Left
    GEOMETRY_HANDLING = Use Left
    JOINED -> AttributeRemover_ClearUnnecessary
Note: Remove unwanted attributes
AttributeRemover_ClearUnnecessary
    REMOVE_ATTRS = __response_body,__dummyvalue,__http_status_code,__creation_instance,__authorizationkey
    -> OutputWithToken (output)
OutputWithToken (output)

Bookmark: Autorization Key
Note: Create and encode the authorization string from the consumer key and consumer secret
AttributeCreator_AuthorizationKey
    ATTR_TABLE = SET_TO __authorizationkey = $(API_KEY):$(API_SECRET)
    -> TextEncoder_AuthorizationKey
TextEncoder_AuthorizationKey
    DEST_ATTR = __authorizationkey
    ENCODING_TYPE = BASE64_ENCODE
    STRING_TO_ENCODE = @Value(__authorizationkey)
    -> HTTPCaller_GenerateAccessToken
